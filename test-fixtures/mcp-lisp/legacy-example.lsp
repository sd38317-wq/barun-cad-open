; 바른캐드 실제 AutoLISP 예제 · 좌표 단위 mm
(defun c:BCIRCLE (/ p r)
  (setq p (getpoint "\nCenter X,Y: ") r (getdist p "\nRadius: "))
  (if (and p r (> r 0)) (entmakex (list '(0 . "CIRCLE") (cons 10 p) (cons 40 r)))) (princ))
(defun c:BBOX (/ p q)
  (setq p (getpoint "\nFirst X,Y: ") q (getcorner p "\nOpposite X,Y: "))
  (if (and p q) (command "_.RECTANG" p q)) (princ))
(defun c:BNUMBER (/ ss i p n h e)
  (setq ss (ssget "_I") n (getint "\nStart number: ") h (getdist "\nText height: ") i 0)
  (if (and ss n h) (repeat (sslength ss)
    (setq e (entget (ssname ss i)) p (cdr (assoc 10 e)))
    (if p (progn (entmakex (list '(0 . "TEXT") (cons 10 p) (cons 40 h) (cons 1 (itoa n)))) (setq n (1+ n))))
    (setq i (1+ i)))) (princ))
(defun c:BLENGTH (/ ss i total e a b)
  (setq ss (ssget "_X" '((0 . "LINE"))) i 0 total 0.0)
  (if ss (repeat (sslength ss) (setq e (entget (ssname ss i)) a (cdr (assoc 10 e)) b (cdr (assoc 11 e)) total (+ total (distance a b)) i (1+ i))))
  (princ (strcat "\nTOTAL LENGTH mm = " (rtos total 2 3))) (princ))
